' REF: https://www.cadlinecommunity.co.uk/hc/en-us/articles/201896512-Inventor-2015-iLogic-Clean-Up-Vault-Workspace
' Author: Filemon Salas
' 05/18/2015


Imports System
Imports System.IO
Imports System.Text
	
Sub Main
	oDoc = ThisDoc.Document
	Dim SearchLocation As String = "C:\Inventor Working\Designs"
	Dim filelist As New List(Of String)
	Call GetAllReadOnlyFiles(SearchLocation, filelist)
	
	If filelist.count > 0 Then
		i = MessageBox.Show(filelist.count & " Read-Only file(s) found - Do you Want to Delete Them?" & vbLf & vbLf & _
	 "Note: Make sure there are no files checked-out to you before proceding." & vbLf & vbLf & _
	 "It cannot be guaranteed that read-only files are actually checked into Vault and exist in the Vault database", _
	  "Kenall iLogic",MessageBoxButtons.YesNo,MessageBoxIcon.Question)
	 	If i = vbNo Then
	 		Return
	 	End If
	 Else
	 
	 MessageBox.Show("Your 'Inventor Working' folder appears to be CLEANED. No Read-Only files were found.", "Kenall iLogic")
	 Return
	 
	End If
	 
	For Each strfile As String In filelist
		System.IO.File.SetAttributes(strfile, IO.FileAttributes.Normal)
		System.IO.File.Delete(strfile)
	Next
End Sub
Sub GetAllReadOnlyFiles(ByVal SearchLocation As String, ByRef filelist As List(Of String))
    
        For Each file As String In Directory.GetFiles(SearchLocation)
            Dim attributes = IO.File.GetAttributes(file)
               If ((attributes And FileAttributes.ReadOnly) = FileAttributes.ReadOnly) Then    
                filelist.add(file)
            End If
        Next
        
        For Each dir As String In Directory.GetDirectories(SearchLocation)
            If Not dir.Contains("_V") Then
                Try
                    GetAllReadOnlyFiles(dir, filelist)
                Catch
                End Try
            Else
            End If
        Next
        
 End Sub
