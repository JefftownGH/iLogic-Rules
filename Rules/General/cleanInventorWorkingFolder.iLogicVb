'http://www.dotnetperls.com/recursive-file-directory-vbnet

Imports System.IO

Public Class FileHelper

    Public Shared Function GetFilesRecursive(ByVal initial As String) As List(Of String)
	' This list stores the results.
	Dim result As New List(Of String)

	' This stack stores the directories to process.
	Dim stack As New Stack(Of String)

	' Add the initial directory
	stack.Push(initial)

	' Continue processing for each stacked directory
	Do While (stack.Count > 0)
	    ' Get top directory string
	    Dim dir As String = stack.Pop
	    Try
		' Add all immediate file paths
		result.AddRange(Directory.GetFiles(dir, "*.*"))

		' Loop through all subdirectories and add them to the stack.
		Dim directoryName As String
		For Each directoryName In Directory.GetDirectories(dir)
		    stack.Push(directoryName)
		Next

	    Catch ex As Exception
	    End Try
	Loop

	' Return the list
	Return result
    End Function

End Class




Sub Main()
	' Get recursive List of all files starting in this directory.
		Dim list As List(Of String) = FileHelper.GetFilesRecursive("C:\Inventor Working\Designs\")
		
		If list.Count > 0 Then
		
			' Loop through and display each path.
			For Each path In list
				MessageBox.Show(list.Count,"Folders")
				'show path
				'MessageBox.Show(path,"Folders")
				
				'delete file at path
				My.Computer.FileSystem.DeleteFile(path)
			Next
			
		Else
				MessageBox.Show(list.Count,"Working Directory")
			
		End If

	
End Sub
